FME workspace MapTilesConverter.fmw
Startup Python:
      ''' Startup script for conversion from CMYK input tiles to RGB.
          input map data: .tif data including world files .tfw
          additional inputs: .icc color profile
          output data: PNG map tiles and .pgw world files
          author: Michal Lupa
      '''

      import fme, shutil, os
      from PIL import Image, ImageCms

      inputDataDirectory = fme.macroValues['input_folder']
      destinationDataDirectory = fme.macroValues['output_folder']
      colorProfilesDirectory = fme.macroValues['color_folder']
      mapType = fme.macroValues['map_type']

      Image.MAX_IMAGE_PIXELS = None # off Pillow's pixel limitation during processing

      if mapType not in ('250k', 'Miniscale', 'Overview'): # check if map type has appropriate scale; proper input scales are: 25k and 50k, bigger scales are not sufficient to preprocessing using pyhon PIL
          for filename in os.listdir(inputDataDirectory):
              if filename.lower().endswith("tif"): # filtering tif's, if neccessary - expand it with other raster formats

                  file_path = os.path.join(inputDataDirectory, filename)
                  output_path = os.path.join(destinationDataDirectory, 'out_' + filename.lower().replace('.tif','.png'))
                  print("Tile: " + output_path + " converted!")
                  # color conversion using PIL and .icc profile
                  img = Image.open(file_path)
                  img = ImageCms.profileToProfile(img, colorProfilesDirectory + '\OS_Map_uncoated_FOGRA29_GCR_bas.icc', colorProfilesDirectory + '\sRGB Color Space Profile.icm', renderingIntent=0, outputMode='RGB')
                  img.save(output_path, quality=95) # according to the PIL documentation, max quality is equal to 95

              elif filename.lower().endswith('tfw'): # filtering world files, tfw is connected with tiff's, for other world file formats see https://en.wikipedia.org/wiki/World_file
                  file_path = os.path.join(inputDataDirectory, filename)
                  output_path = os.path.join(destinationDataDirectory, 'out_' + filename.lower().replace('.tfw','.pgw')) # replacing extension - pgw's are connected with png
                  shutil.copy(file_path, output_path)

              else:
                  continue

Parameters:
- input_folder = C:\Users\spyrosoft\Desktop\Data\25k\25K660_TIFF_PART1\data\hu   # input data directory
- color_folder = C:\Users\spyrosoft\Desktop\OS\ETL   # color profiles directory
- map_type = 25k   # input map scale
- output_folder = C:\Users\spyrosoft\Desktop\NewTiles\25k\hu   # output directory

Creator
    GEOMTYPE = Geometry Object
    NUM = 1
    CREATED -> Tester_2
Tester_2
    BOOL_OP = OR
    COMPOSITE_TEST = 1
    TEST_CLAUSE = TEST $(map_type) IN 25k,50k
    TEST_MODE = TEST
    PASSED -> FeatureReader_2 [INITIATOR]
    FAILED -> FeatureReader [INITIATOR]
FeatureReader_2
    ATTRIBUTES = PNGRASTER,
    ATTR_ACCUM_MODE = Only Use Result
    COMBINE_GEOM = Use Result
    COORDSYS = EPSG:27700
    DATASET = $(output_folder)\*.png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    <OTHER> -> RasterPropertyExtractor
FeatureReader
    ATTRIBUTES = GEOTIFF,
    ATTR_ACCUM_MODE = Only Use Result
    COMBINE_GEOM = Use Result
    COORDSYS = EPSG:27700
    DATASET = $(input_folder)\*.tif
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = <No Spatial Filter>
    OUTPUT_FEATURES_DISPLAY = Schema and Data Features
    <OTHER> -> RasterPropertyExtractor
RasterPropertyExtractor
    -> Tester
Tester
    BOOL_OP = OR
    COMPOSITE_TEST = 1
    TEST_CLAUSE = TEST $(map_type) IN 250k, Miniscale, Overview
    TEST_MODE = TEST
    PASSED -> RasterPaletteResolver
    FAILED -> RasterMosaicker
RasterPaletteResolver
    -> RasterInterpretationCoercer
RasterInterpretationCoercer
    COLOR_TO_COLOR = Scale by data type
    FLOAT_TO_INTEGER = Round
    INTERPRETATION = RGBA64
    NUMERIC_TO_COLOR = Scale by data values
    RGB_TO_RGBA = Create opaque alpha band
    -> RasterMosaicker
RasterMosaicker
    ACCUM_ATTRS_NAME = Use Attributes From One Feature
    INTERPOLATION_TYPE_NAME = Bicubic
    MERGE_PALETTES_NAME = Yes
    NODATA_OVERWRITE = Yes
    OVERLAPPING_VALUES = last
    SNAPPING_TYPE_NAME = Resample
    -> Reprojector
Reprojector
    DEST = EPSG:3857
    INTERPOLATION_TYPE_NAME = Bilinear
    RASTER_CELL_SIZE = Square Cells
    RASTER_TOLERANCE = 0.0
    SOURCE = Read from feature
    REPROJECTED -> AttributeCreator
AttributeCreator
    ATTR_TABLE:
      SET_TO min_zoom = FME_CONDITIONAL:DEFAULT_VALUE'_FME_NO_OP_'BOOL_OP;OR;COMPOSITE_TEST;1;TEST $(map_type) = 25k'15'BOOL_OP;OR;COMPOSITE_TEST;1;TEST $(map_type) = 50k'13'BOOL_OP;OR;COMPOSITE_TEST;1;TEST $(map_type) = 250k'11'BOOL_OP;OR;COMPOSITE_TEST;1;TEST $(map_type) = Miniscale'9'BOOL_OP;OR;COMPOSITE_TEST;1;TEST $(map_type) = Overview'6'FME_NUM_CONDITIONS6___
      SET_TO max_zoom = FME_CONDITIONAL:DEFAULT_VALUE'_FME_NO_OP_'BOOL_OP;OR;COMPOSITE_TEST;1;TEST $(map_type) = 25k'16'BOOL_OP;OR;COMPOSITE_TEST;1;TEST $(map_type) = 50k'14'BOOL_OP;OR;COMPOSITE_TEST;1;TEST $(map_type) = 250k'12'BOOL_OP;OR;COMPOSITE_TEST;1;TEST $(map_type) = Miniscale'10'BOOL_OP;OR;COMPOSITE_TEST;1;TEST $(map_type) = Overview'8'FME_NUM_CONDITIONS6___
    -> WebMapTiler
    -> ConcurrentWebMapTiler
WebMapTiler [off]
    INTERPOLATION_TYPE_NAME = Bilinear
    MAX_ZOOM_LEVEL = @Value(max_zoom)
    MIN_ZOOM_LEVEL = @Value(min_zoom)
    NUM_TILES_ATTRIBUTE = _num_tiles
    QUADKEY_ATTRIBUTE = _quadkey
    RASTER_INDEX_ATTRIBUTE = _raster_index
    TILE_COLUMN_ATTRIBUTE = _tile_column
    TILE_ROW_ATTRIBUTE = _tile_row
    TILE_SCHEME = GoogleMapsCompatible
    ZOOM_LEVEL_ATTRIBUTE = _zoom_level
    TILES -> AttributeCreator_2
ConcurrentWebMapTiler
    MAX_ZOOM = @Value(max_zoom)
    MIN_ZOOM = @Value(min_zoom)
    -> AttributeCreator_2
AttributeCreator_2
    ATTR_TABLE = SET_TO outputPath = $(output_folder)\@Value(_zoom_level)\@Value(_tile_column)
    -> ConcurrentFeatureWriter
    -> FeatureWriter [Output]
FeatureWriter [off]
    COORDSYS = EPSG:3857
    DATASET = @Value(outputPath)
    DATASET_ATTR = _dataset
    FEATURE_TYPE_LIST_ATTR = _feature_type
    FORMAT = PNGRASTER
    TOTAL_FEATURES_WRITTEN_ATTR = _total_features_written
ConcurrentFeatureWriter
    OUTPUTPATH = @Value(outputPath)
    _TILE_COLUMN = @Value(_tile_column)

FME custom transformer ConcurrentFeatureWriter

Parameters:
- OUTPUTPATH = @Value(outputPath)   # outputPath
- FME_PROCESS_GROUP_BY =   # "" Group By
- FME_PROCESS_GROUPS_ORDERED = No   # Process At End (Blocking),No%Process When Group Changes (Advanced),Yes Group By Mode
- _TILE_COLUMN = @Value(_tile_column)   # Tile Column

Input (input)
    -> FeatureWriter_2 [Output]
FeatureWriter_2
    COORDSYS = EPSG:3857
    DATASET = @Value(outputPath)
    DATASET_ATTR = _dataset
    FEATURE_TYPE_LIST_ATTR = _feature_type
    FORMAT = PNGRASTER
    TOTAL_FEATURES_WRITTEN_ATTR = _total_features_written
    SUMMARY -> Output (output)
Output (output)

FME custom transformer ConcurrentWebMapTiler

Parameters:
- FME_PROCESS_GROUP_BY =   # "" Group By
- FME_PROCESS_GROUPS_ORDERED = No   # Process At End (Blocking),No%Process When Group Changes (Advanced),Yes Group By Mode
- MAX_ZOOM = @Value(max_zoom)   # Max Zoom
- MIN_ZOOM = @Value(min_zoom)   # Min Zoom

Input (input)
    -> WebMapTiler
WebMapTiler
    INTERPOLATION_TYPE_NAME = Bilinear
    MAX_ZOOM_LEVEL = @Value(max_zoom)
    MIN_ZOOM_LEVEL = @Value(min_zoom)
    NUM_TILES_ATTRIBUTE = _num_tiles
    QUADKEY_ATTRIBUTE = _quadkey
    RASTER_INDEX_ATTRIBUTE = _raster_index
    TILE_COLUMN_ATTRIBUTE = _tile_column
    TILE_ROW_ATTRIBUTE = _tile_row
    TILE_SCHEME = GoogleMapsCompatible
    ZOOM_LEVEL_ATTRIBUTE = _zoom_level
    TILES -> Output (output)
Output (output)
